package L14_2_PackageCommonTypes {

// ============================================================================
// SUBPACKAGE: Common Types
// ============================================================================

package CommonTypes {
        public enum def Color {
            enum red;
            enum gold;
            enum white;
            enum brown;
            enum blue;
        }

        public enum def SkillType {
            enum assembly;
            enum navigation;
            enum magic;
        }

        public part def Person;
        public part def Hallway;
    }
}
